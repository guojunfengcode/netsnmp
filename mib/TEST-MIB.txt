TEST-MIB DEFINITIONS ::= BEGIN

IMPORTS
      OBJECT-GROUP, MODULE-COMPLIANCE, NOTIFICATION-GROUP              FROM SNMPv2-CONF
      enterprises, Integer32, OBJECT-TYPE, MODULE-IDENTITY, Gauge32,
      OBJECT-IDENTITY, NOTIFICATION-TYPE                               FROM SNMPv2-SMI
      TimeStamp                                                        FROM SNMPv2-TC
	  DisplayString    												   FROM SNMPv2-TC
;
        
testData MODULE-IDENTITY
      LAST-UPDATED "201511111040Z"
      ORGANIZATION
           "Organization."
      CONTACT-INFO
           "Contact-info."
      DESCRIPTION
           "Description."
      ::= { enterprises 1006 }
      
-- node defintions
   
data1 OBJECT IDENTIFIER ::= { testData 1 }

ddata1 OBJECT IDENTIFIER ::= { data1 1 }
ddata2 OBJECT IDENTIFIER ::= { data1 2 }

   
getData1 OBJECT-TYPE
         SYNTAX Integer32 
         MAX-ACCESS read-write
         STATUS current
         DESCRIPTION
               "Description."
         DEFVAL { 4 }
         ::= { ddata1 1 }
       
       
getddata1 OBJECT-TYPE
         SYNTAX  DisplayString (SIZE(0..8)) 
         MAX-ACCESS read-write
         STATUS current
         DESCRIPTION
               "Description."
         ::= { ddata1 2 }        
       
getddata2 OBJECT-TYPE
         SYNTAX OCTET STRING (SIZE(0..8)) 
         MAX-ACCESS read-write
         STATUS current
         DESCRIPTION
               "Description."
         ::= { ddata2 1 } 
		 
END
