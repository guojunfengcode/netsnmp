TEST-TRAP-MIB DEFINITIONS ::= BEGIN
IMPORTS
	OBJECT-GROUP, MODULE-COMPLIANCE, NOTIFICATION-GROUP              FROM SNMPv2-CONF
	enterprises, Integer32, OBJECT-TYPE, MODULE-IDENTITY, Gauge32,
	OBJECT-IDENTITY, NOTIFICATION-TYPE                               FROM SNMPv2-SMI
	TimeStamp                                                        FROM SNMPv2-TC
;

trapTest MODULE-IDENTITY
	LAST-UPDATED "201511121031Z"
	ORGANIZATION
		"Organization."
	CONTACT-INFO
		"Contact-info."
	DESCRIPTION
		"Description."
	::= { enterprises 1005 }

-- node defintions
datamodule OBJECT IDENTIFIER ::= { trapTest 1 }
trapmodule OBJECT IDENTIFIER ::= { trapTest 2 }
--notedata OBJECT IDENTIFIER ::= { trapTest 3 }


data OBJECT IDENTIFIER ::= { datamodule 1 }
alarm OBJECT IDENTIFIER ::= { trapmodule 1 }

prefix OBJECT IDENTIFIER ::= { alarm 1 }
content OBJECT IDENTIFIER ::= { alarm 2 }

getdata OBJECT-TYPE
	SYNTAX Integer32 
	MAX-ACCESS read-write
	STATUS current
	DESCRIPTION
		"Description."
	DEFVAL { 4 }
	::= { data 1 }

-- SNMP TRAP NOTIFICATION-TYPE
alarmInfo1 NOTIFICATION-TYPE
	OBJECTS { alarmContent }
	STATUS current
	DESCRIPTION
		"Description."
	::= { prefix 1 }

alarmInfo2 NOTIFICATION-TYPE
	OBJECTS { alarmContent }
	STATUS current
	DESCRIPTION
		"Description."
	::= { prefix 2 }

alarmContent OBJECT-TYPE
	SYNTAX OCTET STRING (SIZE(0..1025))
	MAX-ACCESS accessible-for-notify
	STATUS current
	DESCRIPTION
		"告警内容"
	::= { content 1 } 

END
